//---- BEGIN COPYRIGHT -------------------------------------------------------
//
// Copyright (C) 2012 Feuerlabs, Inc. All rights reserved.
//
// This Source Code Form is subject to the terms of the Mozilla Public
// License, v. 2.0. If a copy of the MPL was not distributed with this
// file, You can obtain one at http://mozilla.org/MPL/2.0/.
//
//---- END COPYRIGHT ---------------------------------------------------------
module exoport
{

    namespace "http://feuerlabs.com/exoport";
    prefix exoport;

    description
        "Schema for ExoPort Core protocol carried over BERT-RPC. All calls " +
        "are prefixed with ep- (exoport) to denote them from app-specific "+
        "extensions to the protocol.";

    typedef image-id-type {
        type string {
            length "1..256";
        }

        description "An Image ID.";
    }

    typedef result-code {
        type enumeration {
	    enum ok {
		description "Operation was successful.";
		value 0;
	    }

	    enum illegal-size {
		description "An incorrect size was used for the operation.";
		value 1;
	    }

	    enum object-not-found {
		description "The object referenced was not found.";
		value 2;
	    }

	    enum checksum-failure {
		description
                    "The checksum/signature validation failed.";
		value 3;
	    }

	    enum permission-denined {
		description
		  "The operation is not allowed to be carried out.";
		value 4;
	    }


	    enum unsupported {
		description
		  "The operation is not supported by the receievr. ";
		value 5;
	    }

	    enum format-error {
		description "The RPC has an incorrect format element structure.";
		value 6;
	    }

	    enum value-error {
		description
		  "The RPC has illegal values in one or more of its arguments.";
		value 7;
            }
	    enum dependency-failure {
		description
                    "Dependencies could not be resolved in order to carry out the operation.";
		value 8;
	    }
	}
        description
	  "Exoport result codes.";
    }

    //
    // Image types supported by the protocol
    // NOT CURRENTLY USED - MAY NEVER BE USED.
    //
    typedef ep-image-type {

        type enumeration {
	    enum configuration-data {
		description "Image contains configurtion data.";
		value 0;
	    }

	    enum rpm-file {
		description "The image contains an RPM file";
		value 1;
	    }

	    enum debian-file {
		description "The image contains a debian file.";
		value 2;
	    }
	    enum other {
		description "The image contains other type of file.";
		value 3;
	    }
	}
        description
	  "Define image types to be transferred over the protocol.";
    }

    rpc ep-start-image-transfer {
        description
            "Start a transfer of a new image with the given name. " +
            "Any earlier images with the same name, regardless of type, " +
            "will be truncated and reset. " +
            "When this call has returned successfully, transfer-image-chunk " +
            "can be called to transmit sections of the image until it is " +
            "complete. " +
            "The image is divided into chunks, with a size defined by " +
            "this call. Each chunk will be addressed by an index ranging " +
            "0 to int(image-size /chunk-size). " +
            "The chunk transfer will continue (with the possible overwriting of " +
            "earlier transmitted chunks) until a ep-finhish-image-transfer call " +
            "is made. At that point checksumming and validation is done by the receiver "+
            "who will then return wether the image was trasnferred correctly OK or not." +
            "If the image size is -1, streaming, chunks will be " +
            "transmitted with the chunk-index ignored. ";

	input {
            leaf image-id {
                description "ID to reference the image by. (File name)";
                type image-id-type;
            }

            leaf image-type {
                description "Type of image.";
                type ep-image-type;
            }


            leaf image-size {
                description
                    "Total image size, in bytes. -1 = streaming.";

                type int32;
            }

            leaf chunk-size {
                description
                    "Number of bytes in each chunk. Set to 0 for streaming images.";
                type int32;
            }
	}

	output {
            leaf result {
                type result-code;
            }
	}
    }

    rpc ep-transfer-image-chunk {
        description
            "Transfer a chunk of the image to the other side" +
            "The chunk index specifies which secion of the file is being transmitted." +
            "The file offset where the chunk is to be written is calculated as: " +
            "chunk-size * chunk-index. All chunks except the last one " +
            "(chunk-index == int(image-size/chunk-size)) must have a size set to the " +
            "chunk size of the image. The size of the last chunk must be set to " +
            "image-size % chunk-size bytes, unless the size would be 0. In that " +
            "case the last chunk is to be omitted. " +
            "If image is streaming (image-size == -1), the size of each chunk can " +
            "vary, but not 0. The image streaming will be complete when a chunk "+
            "sized at zero bytes is transferred.";
	input {
            leaf image-id {
                description "ID to reference the image by. (File name)";
                type image-id-type;
            }

            leaf chunk-index {
                description "Index of chunk.";
                type uint32;
            }

            leaf size {
                description
                    "Size of this chunk. Should always be " +
                    "ep-start-image-chunk-transfer:chunk-size, except for the last chunk.";
                type uint32;
            }
	}

	output {
            leaf result {
                type result-code;
            }
	}
    }

    rpc ep-finish-image-tranfer {
        description
            "Complete a chunk transfer. The recipient will check that all chunks " +
            "have been received and that the file checksum matches the checksum provided " +
            "by this rpc. The result of the validation is sent back with the reply of " +
            "this rpc. ";
	input {
            leaf image-id {
                type image-id-type;
                description "ID to reference the image by. (File name)";
            }

            leaf checksum {
                description "Checksum for image. Can be signature.";
                type string;
            }
	}

	output {
            leaf result {
                type result-code;
            }
	}
    }


    rpc ep-delete-image {
        description
            "Delete a complete or partially transferred image from the receiving system." +
            "If the image is still being transferred (ep-finish-image-transfer has not yet "+
            "been called, no more chunks or ep-finish-image-transfer calls will be accepted " +
            "for this image.";
	input {
            leaf image-id {
                type image-id-type;
                description "ID to reference the image by. (File name)";
            }
	}

	output {
            leaf result {
                type result-code;
            }
	}
    }

    rpc ep-install-packages {
        description
            "Installs one or more images transferred earlier.";
	input {
            leaf-list images {
                description "ID to reference the image by. (File name)";
                type image-id-type;
            }
	}

	output {
            leaf result {
                type result-code;
            }
	}
    }

    rpc ep-upgrade-packages {
        description
            "Upgrades one or more packages from the images transferred earlier.";
	input {
            leaf-list images {
                description "ID to reference the image by. (File name)";
                type image-id-type;
            }
	}

	output {
            leaf result {
                type result-code;
            }
	}
    }

    rpc ep-uninstall-packages {
        description
            "Upgrades one or more packages from the images transferred earlier.";
	input {
            leaf-list images {
                description "ID to reference the image by. (File name)";
                type image-id-type;
            }
	}

	output {
            leaf result {
                type result-code;
            }
	}
    }

    //
    // CONFIG SYSTEM RPCs
    //
    rpc ep-activate-config {
        description
            "Activates a configuration stored in an image. " +
            "The configuration is atomically switched in. " +
            "Please note that the active configuration does not exist as an image, " +
            "but instead resides outside the image namespace. " +
            "The configuration active at the time this command is executed will be moved " +
            "to a backup position (also outside the image namespace), and can be recalled " +
            "with a ep-rollback-config command.";
	input {
            leaf image-id {
                description "ID of image to activate";
                type image-id-type;
            }
	}

	output {
            leaf result {
                type result-code;
            }
	}
    }

    rpc ep-rollback-config {
        description
            "Switch back to the previously active configuration. " +
            "The previous configuration is atomically switched in. " +
            "The configuration active when this call is made will become the backup. " +
            "In effect, the active and backup configuration images will switch places.";

	output {
            leaf result {
                type result-code;
            }
	}
    }
}
